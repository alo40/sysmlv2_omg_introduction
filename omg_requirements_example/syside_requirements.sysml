private import SI::*;
package 'Syside Requirement Example' {
    part def Vehicle {
        attribute dryMass : MassValue;
        attribute fuelMass : MassValue;
        attribute fuelFullMass : MassValue;
    }
    part vehicle_c1 : Vehicle {
        attribute :>> dryMass = 1500 [kg];
        attribute :>> fuelMass = 20 [kg];
        attribute :>> fuelFullMass = 40 [kg];
        satisfy vehicleSpecification by vehicle_c1;
    }
    requirement vehicleSpecification {
        doc
        /* Overall vehicle requirements group */
        subject param : Vehicle;
        require fullVehicleMassLimit { in sub = param; }
        require emptyVehicleMassLimit { in sub = param; }
    }
    requirement def MassLimitationRequirement {
        doc
        /* The actual mass shall be less than or equal to the required mass. */
        attribute massActual : MassValue;
        attribute massReqd : MassValue;
        require constraint { massActual <= massReqd }
    }
    requirement def <'1'> VehicleMassLimitationRequirement :> MassLimitationRequirement {
        doc
        /* The total mass of a vehicle shall be less than or equal to the required mass. */
        subject vehicle : Vehicle;
        attribute :>> massActual = vehicle.dryMass + vehicle.fuelMass;
        assume constraint { vehicle.fuelMass > 0 [kg] }
    }
    requirement <'1.1'> fullVehicleMassLimit : VehicleMassLimitationRequirement {
        subject vehicle : Vehicle;
        attribute :>> massReqd = 2000 [kg];
        assume constraint {
            doc
            /* Fuel tank is full. */
            vehicle.fuelMass == vehicle.fuelFullMass
        }
    }
    requirement <'1.2'> emptyVehicleMassLimit : VehicleMassLimitationRequirement {
        subject vehicle : Vehicle;
        attribute :>> massReqd = 1500 [kg];
        assume constraint {
            doc
            /* Fuel tank is empty. */
            vehicle.fuelMass == 0 [kg]
        }
    }
}
